module iana-quic-transport {
  yang-version 1.1;
  namespace "urn:ietf:params:xml:ns:yang:iana-quic-transport";
  prefix iana-quic-transport;

  organization
    "Internet Assigned Numbers Authority (IANA)";

  contact
    "Internet Assigned Numbers Authority

     ICANN
     12025 Waterfront Drive, Suite 300
     Los Angeles, CA 90094
     

     Tel: +1 424 254 5300

     <mailto:iana@iana.org>";

  description
    "This YANG module translates IANA registry 'QUIC Transport
     Parameters' to YANG derived types.

     Copyright (c) 2024 IETF Trust and the persons identified as
     authors of the code. All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module was generated from the
     corresponding IANA registry using an XSLT stylesheet from the
     'iana-yang' project (https://github.com/llhotka/iana-yang).";

  reference
    "QUIC (https://www.iana.org/assignments/quic/)";

  revision 2024-03-21 {
    description
      "Current revision as of the revision date specified in the XML
       representation of the registry page.";
    reference
      "https://www.iana.org/assignments/quic/quic.xml";
  }

  /* Typedefs */

  typedef quic-transport-parameter {
    type enumeration {
      enum original_destination_connection_id {
        value 0x00;
        description
          "(permanent)";
        reference
          "RFC 9000";
      }
      enum max_idle_timeout {
        value 0x01;
        description
          "(permanent)";
        reference
          "RFC 9000";
      }
      enum stateless_reset_token {
        value 0x02;
        description
          "(permanent)";
        reference
          "RFC 9000";
      }
      enum max_udp_payload_size {
        value 0x03;
        description
          "(permanent)";
        reference
          "RFC 9000";
      }
      enum initial_max_data {
        value 0x04;
        description
          "(permanent)";
        reference
          "RFC 9000";
      }
      enum initial_max_stream_data_bidi_local {
        value 0x05;
        description
          "(permanent)";
        reference
          "RFC 9000";
      }
      enum initial_max_stream_data_bidi_remote {
        value 0x06;
        description
          "(permanent)";
        reference
          "RFC 9000";
      }
      enum initial_max_stream_data_uni {
        value 0x07;
        description
          "(permanent)";
        reference
          "RFC 9000";
      }
      enum initial_max_streams_bidi {
        value 0x08;
        description
          "(permanent)";
        reference
          "RFC 9000";
      }
      enum initial_max_streams_uni {
        value 0x09;
        description
          "(permanent)";
        reference
          "RFC 9000";
      }
      enum ack_delay_exponent {
        value 0x0a;
        description
          "(permanent)";
        reference
          "RFC 9000";
      }
      enum max_ack_delay {
        value 0x0b;
        description
          "(permanent)";
        reference
          "RFC 9000";
      }
      enum disable_active_migration {
        value 0x0c;
        description
          "(permanent)";
        reference
          "RFC 9000";
      }
      enum preferred_address {
        value 0x0d;
        description
          "(permanent)";
        reference
          "RFC 9000";
      }
      enum active_connection_id_limit {
        value 0x0e;
        description
          "(permanent)";
        reference
          "RFC 9000";
      }
      enum initial_source_connection_id {
        value 0x0f;
        description
          "(permanent)";
        reference
          "RFC 9000";
      }
      enum retry_source_connection_id {
        value 0x10;
        description
          "(permanent)";
        reference
          "RFC 9000";
      }
      enum version_information {
        value 0x11;
        description
          "(permanent)";
        reference
          "RFC 9368";
      }
      enum max_datagram_frame_size {
        value 0x20;
        description
          "(permanent)";
        reference
          "RFC 9221";
      }
      enum discard {
        value 0x173e;
        description
          "(provisional) Receiver silently discards.";
        reference
          "https://github.com/quicwg/base-drafts/wiki
           /Quantum-Readiness-test";
      }
      enum google_handshake_message {
        value 0x26ab;
        description
          "(provisional) Used to carry Google internal handshake
           message";
      }
      enum grease_quic_bit {
        value 0x2ab2;
        description
          "(permanent)";
        reference
          "RFC 9287";
      }
      enum initial_rtt {
        value 0x3127;
        description
          "(provisional) Initial RTT in microseconds";
      }
      enum google_connection_options {
        value 0x3128;
        description
          "(provisional) Google connection options for
           experimentation";
      }
      enum user_agent {
        value 0x3129;
        status deprecated;
        description
          "(provisional) User agent string (deprecated)";
      }
      enum google_version {
        value 0x4752;
        description
          "(provisional) Google QUIC version downgrade prevention";
      }
      enum version_information_draft {
        value 0xff73db;
        status deprecated;
        description
          "(provisional) Deprecated; use version_information
           instead";
        reference
          "draft-ietf-quic-version-negotiation-13";
      }
      enum min_ack_delay {
        value 0xff04de1b;
        description
          "(provisional)";
        reference
          "draft-ietf-quic-ack-frequency-07";
      }
      enum enable_multipath {
        value 0x0f739bbc1b666d05;
        description
          "(provisional)";
        reference
          "draft-ietf-quic-multipath-05";
      }
      enum enable_multipath-06 {
        value 0x0f739bbc1b666d06;
        description
          "(provisional)";
        reference
          "draft-ietf-quic-multipath-06";
      }
      enum bdp_frame {
        value 0x4143414213370002;
        description
          "(provisional)";
        reference
          "draft-misell-quic-bdp-token-02";
      }
    }
    description
      "This enumeration type defines QUIC transport parameters.";
    reference
      "RFC 9000: QUIC: A UDP-Based Multiplexed and Secure
       Transport";
  }

  typedef transport-parameter {
    type quic-transport-parameter;
    description
      "This type allows reference to a QUIC transport parameters
       using the assigned value.";
  }
}
