module iana-quic-versions {
  yang-version 1.1;
  namespace "urn:ietf:params:xml:ns:yang:iana-quic-versions";
  prefix iana-quic-versions;

  organization
    "Internet Assigned Numbers Authority (IANA)";

  contact
    "Internet Assigned Numbers Authority

     ICANN
     12025 Waterfront Drive, Suite 300
     Los Angeles, CA 90094
     

     Tel: +1 424 254 5300

     <mailto:iana@iana.org>";

  description
    "This YANG module translates IANA registry 'QUIC Versions' to
     YANG derived types.

     Copyright (c) 2024 IETF Trust and the persons identified as
     authors of the code. All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module was generated from the
     corresponding IANA registry using an XSLT stylesheet from the
     'iana-yang' project (https://github.com/llhotka/iana-yang).";

  reference
    "QUIC (https://www.iana.org/assignments/quic/)";

  revision 2024-03-21 {
    description
      "Current revision as of the revision date specified in the XML
       representation of the registry page.";
    reference
      "https://www.iana.org/assignments/quic/quic.xml";
  }

  /* Typedefs */

  typedef quic-version {
    type enumeration {
      enum 0x00000000 {
        description
          "(permanent) Reserved for Version Negotiation";
        reference
          "RFC 9000";
      }
      enum 0x00000001 {
        description
          "(permanent)";
        reference
          "RFC 9000";
      }
      enum 0x51303433 {
        description
          "(provisional) Google QUIC Q043";
      }
      enum 0x51303436 {
        description
          "(provisional) Google QUIC Q046";
      }
      enum 0x51303530 {
        description
          "(provisional) Google QUIC Q050";
      }
      enum 0x6b3343cf {
        description
          "(permanent)";
        reference
          "RFC 9369";
      }
      enum 0x709a50c4 {
        description
          "(provisional) QUIC v2 draft codepoint";
        reference
          "RFC 9369";
      }
    }
    description
      "This enumeration type defines QUIC protocol versions.";
    reference
      "RFC 9000: QUIC: A UDP-Based Multiplexed and Secure
       Transport";
  }

  typedef version {
    type quic-version;
    description
      "This type allows reference to a QUIC version using the
       assigned value.";
  }
}
