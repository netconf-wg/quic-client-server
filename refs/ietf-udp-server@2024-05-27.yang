module ietf-udp-server {
  yang-version 1.1;
  namespace
    "urn:ietf:params:xml:ns:yang:ietf-udp-server";
  prefix udps;
  import ietf-inet-types {
    prefix inet;
    reference
      "RFC 6991: Common YANG Data Types";
  }

  organization "IETF NETCONF (Network Configuration) Working Group";
  contact
    "WG Web:   <http:/tools.ietf.org/wg/netconf/>
     WG List:  <mailto:netconf@ietf.org>

     Authors:  Alex Huang Feng
               <mailto:alex.huang-feng@insa-lyon.fr>
               Pierre Francois
               <mailto:pierre.francois@insa-lyon.fr>";

  description
    "Defines a generic grouping for UDP-based server applications.

    Copyright (c) 2024 IETF Trust and the persons identified as
    authors of the code.  All rights reserved.

    Redistribution and use in source and binary forms, with or without
    modification, is permitted pursuant to, and subject to the license
    terms contained in, the Revised BSD License set forth in Section
    4.c of the IETF Trust's Legal Provisions Relating to IETF Documents
    (https://trustee.ietf.org/license-info).

    This version of this YANG module is part of RFC-to-be; see the RFC
    itself for full legal notices.";

  revision 2024-05-27 {
    description
      "Initial revision";
    reference
      "RFC-to-be: YANG Grouping for UDP Clients and UDP Servers";
  }

  grouping udp-server-grouping {
    description
      "Provides a reusable grouping for configuring a UDP server.

      Note that this grouping uses fairly typical descendant
      node names such that a stack of 'uses' statements will
      have name conflicts.  It is intended that the consuming
      data model will resolve the issue (e.g., by wrapping
      the 'uses' statement in a container called
      'udp-server-parameters').  This model purposely does
      not do this itself so as to provide maximum flexibility
      to consuming models.";

    list local-bind {
      key local-address;
      min-elements 1;
      description
        "A list of bind (listen) points for this server
        instance.  A server instance may have multiple
        bind points to support, e.g., the same port in
        different address families or different ports
        in the same address family.";

      leaf local-address {
        type inet:ip-address;
        mandatory true;
        description
          "The local IP address to listen on for incoming
          UDP messages.  To configure listening
          on all IPv4 addresses the value must be '0.0.0.0'
          (INADDR_ANY).  To configure listening on all IPv6
          addresses the value must be '::' (INADDR6_ANY).";
      }

      leaf local-port {
        type inet:port-number;
        default "0";
        description
          "The local port number to listen on for incoming UDP
          messages.  An invalid default value (0)
          is used (instead of 'mandatory true') so that an
          application level data model may 'refine' it with
          an application specific default port number value.";
      }
    }
  }
}
